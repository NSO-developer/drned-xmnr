module drned-xmnr {
  namespace "http://cisco.com/ns/drned-xmnr";
  prefix drned-xmnr;

  import tailf-common {
    prefix tailf;
  }
  import tailf-ncs {
    prefix ncs;
  }

  description "A Doctor's bag of tools for examining & diagnosing your NSO NEDs";

  grouping action-output-common {
    leaf error {
      type string;
    }
    leaf success {
      type string;
    }
    leaf failure {
      type string;
    }
  }

  grouping conflicts-resolution-choice {
    choice conflicts {
      default overwrite;
      case overwrite {
        leaf overwrite {
          type boolean;
          default false;
        }
      }
      case skip-existing {
        leaf skip-existing {
          type empty;
        }
      }
    }
  }

  typedef filepath-pattern-type {
    type string;
  }
  typedef dirpath-type {
    type string;
  }
  typedef state-file-format {
    type enumeration {
      enum nso-xml {
        tailf:code-name state-nso-xml;
      }
      enum nso-c-style {
        tailf:code-name state-nso-c;
      }
    }
    default nso-xml;
  }

  container drned-xmnr {
    leaf drned-directory {
      tailf:info "DrNED installation directory; either absolute or relative
                  path.  If unset, the built-in DrNED submodule is used";
      type union {
        type enumeration {
          enum builtin {
            tailf:info "Use the built-in DrNED submodule";
          }
          enum env {
            tailf:info "Use the DRNED environment variable";
          }
        }
        type dirpath-type;
      }
      default builtin;
    }
    leaf xmnr-directory {
      tailf:info "Directory where XMNR data is stored; either absolute or
                  relative path.";
      type dirpath-type;
      default "/tmp/xmnr";
    }
    leaf xmnr-log-file {
      tailf:info
        "If set, all output is stored to that file (relative to
         xmnr-directory).  Useful especially if actions are not run
         from the CLI.";
      type string;
    }
    leaf cli-log-file {
      tailf:info
        "If set, all output that would be printed to CLI, goes to that
         file; if run from a CLI session, output is printed both to
         CLI as well as to the file.  The path should be absolute
         (otherwise the file is opened wherever xmnr happens to be
         running).";
      type string;
    }
    tailf:action cli-log-message {
      tailf:hidden "cli-logger";
      tailf:actionpoint xmnr-cli-log;
      tailf:info
        "If registered, all output that would be printed to CLI is
         also sent to the action callback.";
      input {
        leaf device {
          type string;
        }
        leaf message {
          type string;
        }
      }
    }
    container log-detail {
      typedef filter {
        type enumeration {
          enum none {
            tailf:info "No output at all";
          }
          enum overview {
            tailf:info "Only log info about top-level steps";
          }
          enum drned-overview {
            tailf:info "Log info about steps inside DrNED";
          }
          enum all {
            tailf:info "No filtering, everything is logged";
          }
        }
      }
      leaf cli {
        tailf:info "CLI output detail level";
        type filter;
        default drned-overview;
      }
    }
    container last-test-results {
      config false;
      presence last-test;

      leaf device {
        type string;
      }
      list transition {
        leaf from {
          type string;
        }
        leaf to {
          type string;
        }
        container failure {
          presence failure;
          leaf type {
            type enumeration {
              enum load;
              enum commit;
              enum compare;
              enum rollback {
                tailf:code-name rollback_failure;
              }
            }
          }
          leaf message {
            type string;
          }
          leaf comment {
            type string;
          }
        }
      }
    }

    list error-patterns {
      key "match";
      leaf match {
        tailf:cli-expose-key-name;
        type string;
      }
      choice matcher-type {
        mandatory true;
        case exact {
          leaf exact {
            mandatory true;
            type empty;
          }
        }
        case terminated {
          leaf terminator {
            mandatory true;
            type string;
          }
        }
      }
      leaf max-lines {
        type uint8;
      }
    }
  }

  augment /ncs:devices/ncs:device {
    container drned-xmnr {
      leaf cleanup-timeout {
        type uint16;
        default 5;
        tailf:info
          "How long should XMNR wait for a test to do clean-up in case
           of an action abort.";
      }
      leaf driver {
        type string;
        tailf:info
          "Absolute filesystem path to a file of the device driver
           implementation to service the device-dependent DrNED XMNR actions.";
      }
      leaf cli-port {
        type uint16;
        tailf:info
          "Device CLI port number to be passed to the device driver;
           if not set, the NETCONF device port number from the NSO
           device configuration is passed instead.";
      }
      container setup {
        tailf:action setup-xmnr {
          tailf:info
            "Set up XMNR working directory, including setting up
             the DRNED subdirectory";
          tailf:actionpoint drned-xmnr;
          input {
            leaf overwrite {
              tailf:info "Overwrite existing data in the target directory.";
              type boolean;
              default false;
            }
            leaf use-commit-queue {
              tailf:info "Commit queue should be used for testing this
                          device.";
              type boolean;
              default true;
            }
            leaf save-default-config {
              tailf:info "Save current on-device configuration as a new default
                          for state traversals.";
              type boolean;
              default false;
            }
          }
          output {
            uses action-output-common;
          }
        }
      }
      container state {
        grouping state-or-pattern {
          choice state-or-pattern {
            mandatory true;
            leaf state-name {
              type leafref {
                path ../../states/state;
              }
            }
            leaf state-name-pattern {
              type string;
            }
          }
        }
        list states {
          config false;
          tailf:callpoint xmnr-states;
          key state;
          leaf state {
            type string;
          }
          leaf disabled {
            type empty;
          }
        }
        tailf:action record-state {
          tailf:info "Save the current device configuration state in a file. "+
            "A collection of saved state files can later be used with the "+
            "'transitions explore-transitions' command.";
          tailf:actionpoint drned-xmnr;
          input {
            leaf state-name {
              mandatory true;
              type string;
            }
            leaf overwrite {
              type boolean;
              default false;
            }
            leaf including-rollbacks {
              type uint32 {
                range 0..25;
              }
              default 0;
            }
            leaf format {
              type state-file-format;
            }
          }
          output {
            uses action-output-common;
            leaf state-name {
              type leafref {
                path ../../states/state;
              }
            }
          }
        }
        tailf:action delete-state {
          tailf:info "Delete a saved state file. ";
          tailf:actionpoint drned-xmnr;
          input {
            uses state-or-pattern;
          }
          output {
            uses action-output-common;
          }
        }
        tailf:action disable-state {
          tailf:info "Disable a state so that `walk-states' or `explore-states'
                      ignores it.";
          tailf:actionpoint drned-xmnr;
          input {
            uses state-or-pattern;
          }
          output {
            uses action-output-common;
          }
        }
        tailf:action enable-state {
          tailf:info "Enable a disabled state.";
          tailf:actionpoint drned-xmnr;
          input {
            uses state-or-pattern;
          }
          output {
            uses action-output-common;
          }
        }
        tailf:action list-states {
          tailf:info "List the saved states for this device.";
          tailf:actionpoint drned-xmnr;
          input {
          }
          output {
            uses action-output-common;
          }
        }
        tailf:action view-state {
          tailf:info "View a saved state for this device.";
          tailf:actionpoint drned-xmnr;
          input {
            leaf state-name {
              type leafref {
                path ../../states/state;
              }
            }
          }
          output {
            uses action-output-common;
          }
        }
        tailf:action import-state-files {
          tailf:info "Convert a configuration file or files to a XMNR state file.";
          tailf:actionpoint drned-xmnr;
          input {
            leaf file-path-pattern {
              type filepath-pattern-type;
              mandatory true;
            }
            leaf format {
              type enumeration {
                enum xml;
                enum c-style;
                enum nso-xml;
                enum nso-c-style;
              }
              default nso-xml;
            }
            leaf target-format {
              type state-file-format;
            }
            uses conflicts-resolution-choice;
            leaf merge {
              tailf:info "Merge the file(s) with the current configuration
                          before creating the XMNR state file.";
              type boolean;
              default false;
            }
          }
          output {
            uses action-output-common;
          }
        }
        tailf:action import-convert-cli-files {
          tailf:info
            "Given a set of CLI-NED configuration files, convert them
             to NETCONF configuration files and import them as states.
             Note that it also means to successively apply all those
             files.";
          tailf:actionpoint drned-xmnr;
          input {
            leaf file-path-pattern {
              type filepath-pattern-type;
              mandatory true;
            }
            uses conflicts-resolution-choice;
          }
          output {
            uses action-output-common;
          }
        }
        tailf:action check-states {
          tailf:info
            "Check if all configuration files can be still applied
             (e.g. after a device model update).";
          tailf:actionpoint drned-xmnr;
          input {
            leaf validate {
              tailf:info
                "In addition to checking against the device model,
                  validate with the current configuration.";
              type boolean;
              default false;
            }
          }
          output {
            uses action-output-common;
          }
        }
      }
      container transitions {
        grouping transition-states {
          choice states-selection {
            default states;
            leaf-list states {
              tailf:info
                "List of states to pass through (in given order); if
                 empty, all states in random order are used.";
              ordered-by user;
              type leafref {
                path ../../../state/states/state;
              }
            }
            leaf-list ignore-states {
              tailf:info
                "List of states to be ignored for transitions; if used, all
                 states except these ones are used in a random order";
              type leafref {
                path ../../../state/states/state;
              }
            }
          }
        }
        tailf:action transition-to-state {
          tailf:info
            "Change the device state/configuration, possibly with
             rollback.";
          tailf:actionpoint drned-xmnr;
          input {
            leaf state-name {
              type leafref {
                path ../../../state/states/state;
              }
            }
            leaf rollback {
              tailf:info "If true, let DrNED do rollback to the original state";
              type boolean;
              default false;
            }
          }
          output {
            uses action-output-common;
          }
        }
        tailf:action explore-transitions {
          tailf:info
            "Try all possible transitions between states in the state
             set.";
          tailf:actionpoint drned-xmnr;
          input {
            uses transition-states;
            container stop-after {
              tailf:info "Do not start more transitions after given time/coverage has been reached.";
              choice unit-selection {
                leaf seconds { type uint64; }
                leaf minutes { type uint64; }
                leaf hours   { type uint64; }
                leaf days    { type uint64; }
                leaf percent { type uint64; }
                leaf cases   { type uint64; }
              }
            }
          }
          output {
            uses action-output-common;
          }
        }
        tailf:action walk-states {
          tailf:info "Go through all states one after another.";
          tailf:actionpoint drned-xmnr;
          input {
            uses transition-states;
            leaf rollback {
              tailf:info
                "If set to true, after each transition a rollback is
                 performed to the original state.";
              type boolean;
              default false;
            }
          }
          output {
            uses action-output-common;
          }
        }
      }
      container coverage {
        tailf:action reset {
          tailf:info "Reset DrNED coverage data.";
          tailf:actionpoint drned-xmnr;
          output {
            uses action-output-common;
          }
        }
        tailf:action collect {
          tailf:info "Collect DrNED coverage status.";
          tailf:actionpoint drned-xmnr;
          input {
            leaf-list yang-patterns {
              tailf:info
                "Pattern of YANG modules to be used for coverage
                 status.  If empty, the device source YANG modules are
                 used.";
              type string;
            }
          }
          output {
            uses action-output-common;
          }
        }
        container data {
          config false;
          tailf:callpoint coverage-data;

          leaf nodes-total {
            type uint32;
          }
          leaf lists-total {
            type uint32;
          }
          grouping node-coverage {
            container read-or-set {
              uses coverage;
            }
            container set {
              uses coverage;
            }
            container deleted {
              uses coverage;
            }
            container set-set {
              uses coverage;
            }
            container deleted-separately {
              uses coverage;
            }
          }
          grouping coverage {
            leaf total {
              type int32;
            }
            leaf percent {
              type int8;
            }
          }
          container percents {
            container nodes {
              uses node-coverage;
            }
            container lists {
              container read-or-set {
                uses coverage;
              }
              container deleted {
                uses coverage;
              }
              container multi-read-or-set {
                uses coverage;
              }
            }
            container grouping-nodes {
              uses node-coverage;
            }
          }
        }
      }

      typedef target-log-type {
        type enumeration {
          enum device-trace {
            tailf:info "Parse device specfic problems only";
          }
          enum common-xmnr-log {
            tailf:info "Parse all problems from common XMNR log";
          }
        }
      }

      container parsed-problems {
        config false;
        tailf:cli-show-template
            "$(target-log?Parsed log $(target-log),)"
          + "$(target-log?:No log parsed - run device's action: drned-xmnr parse-log-errors.)"
          + "$(parse-time? on $(parse-time),)"
          + "$(count? $(count) problem/s found.)\n";
        leaf target-log {
          type target-log-type;
        }
        leaf parse-time {
          type string;
        }
        leaf count {
          type uint32;
        }
        list problems {
          tailf:cli-suppress-mode;
          tailf:cli-suppress-table;
          tailf:cli-show-template-enter "";
          tailf:cli-show-template-legend
              'Line     Test-Case                                                   '
            + '$(.selected~=phase?Phase       )'
            + '$(.selected~=time?Time)\n'
            + '======================================================================'
            + '$(.selected~=phase?============)'
            +'$(.selected~=time?========================)\n';

          tailf:cli-show-template
              '$(log-line-number|ljust:9)'
            + '$(test-case|ljust:60)'
            + '$(.selected~=phase?$(phase|ljust:12))'
            + '$(.selected~=time?$(time))\n';
          key 'log-line-number';
          leaf log-line-number {
            type uint32;
          }
          leaf test-case {
            type string;
          }
          leaf phase {
            type enumeration {
              enum conversion;
              enum test;
            }
          }
          leaf time {
            type string;
            default "N/A";
          }
          list message-lines {
            tailf:cli-suppress-table;
            tailf:cli-suppress-mode;
            tailf:cli-show-template-enter "";
            tailf:cli-show-template
              '$(line)\n';
            leaf line {
              type string;
            }
          }
        }
      }
      tailf:action load-default-config {
        tailf:info
          "Reset device to the default state by loading a previously stored
           configuration file in native CLI format.";
        tailf:actionpoint drned-xmnr;
        output {
          uses action-output-common;
        }
      }
      tailf:action save-default-config {
        tailf:info "Save the device's running configuration as a default.";
        tailf:actionpoint drned-xmnr;
        output {
          uses action-output-common;
        }
      }
      tailf:action parse-log-errors {
        tailf:info "Shows problems present in XMNR related log files.";
        tailf:actionpoint drned-xmnr;
        input {
          leaf target-log {
            mandatory true;
            type target-log-type;
          }
        }
        output {
          uses action-output-common;
        }
      }
    }
  }
}
